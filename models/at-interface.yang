module interface {

  namespace "https://github.com/alliedtelesis/apteryx";
  prefix interface;

  container interface {
    leaf-list if-alias {
      type string;
      description "Interface index to name";
      config false;
    }
    list interfaces {
      key "name";
      description "Interface List";
      leaf name {
        description "Interface name";
        type string;
      }
      leaf if-index {
        description "Interface Index";
        config false;
        type string;
      }
      container status {
        description "Interface status";
        leaf admin-status {
          description "Admin Status";
          config false;
          default "admin-down";
          type enumeration {
            enum admin-down {
              value 0;
            }
            enum admin-up {
              value 1;
            }
          }
        }
        leaf oper-status {
          description "Operation State, refer: kernel documentation";
          config false;
          type string;
        }
        leaf flags {
          description "Interface state flags, refer: kernel documentation";
          config false;
          type string;
        }
        leaf phys-address {
          description "Physical (MAC) Address";
          config false;
          type string;
        }
        leaf promisc {
          description "Promiscuous mode";
          config false;
          default "promisc-off";
          type enumeration {
            enum promisc-off {
              value 0;
            }
            enum promisc-on {
              value 1;
            }
          }
        }
        leaf qdisc {
          description "Traffic Queuing Discipline";
          config false;
          type string;
        }
        leaf mtu {
          description "Maximum Transmission Unit (68-16535 octets)";
          config false;
          default "1500";
          type int32;
        }
        leaf speed {
          description "Current interface speed (Mb/s)";
          config false;
          default "0";
          type int32;
        }
        leaf duplex {
          description "Current Duplex Mode";
          config false;
          default "Auto";
          type enumeration {
            enum Auto {
              value 0;
              description "Auto Duplex";
            }
            enum Full {
              value 1;
              description "Full Duplex";
            }
            enum Half {
              value 2;
              description "Half Duplex";
            }
          }
        }
        leaf arptype {
          description "ARP Hardware Type";
          config false;
          default "Void";
          type enumeration {
            enum Ethernet {
              value 1;
              description "Ethernet";
            }
            enum Void {
              value 65535;
              description "Void";
            }
          }
        }
        leaf rxq {
          description "How many receive queues exist";
          config false;
          default "1";
          type int32;
        }
        leaf txqlen {
          description "Maximum transmit queue length";
          config false;
          default "1000";
          type int32;
        }
        leaf txq {
          description "How many transmit queues exist";
          config false;
          default "1";
          type int32;
        }
      }
      container settings {
        description "Interface Settings";
        leaf admin-status {
          description "Configured admin status of the port. Refer to status/admin-status for applied value";
          default "admin-up";
          type enumeration {
            enum admin-down {
              value 0;
            }
            enum admin-up {
              value 1;
            }
          }
        }
        leaf mtu {
          description "Maximum Transmission Unit (octets)";
          type string;
        }
      }
      leaf l2 {
        description "1=This is a layer 2 interface";
        config false;
        type enumeration {
          enum unset {
            description "This is not a Layer 2 interface";
            value 0;
          }
          enum l2-if {
            value 1;
            description "This is a Layer 2 interface";
          }
        }
        default unset;
      }
      leaf l3 {
        description "1=This is a layer 3 interface";
        config false;
        type enumeration {
          enum unset {
            description "This is not a Layer 3 interface";
            value 0;
          }
          enum l3-if {
            description "This is a Layer 3 interface";
            value 1;
          }
        }
        default unset;
      }
    }
  }
}
